from pyrateoptics.core.functionobject import FunctionObject
from pyrateoptics.raytracer.localcoordinates import LocalCoordinates
from pyrateoptics.raytracer.surface_shape import Conic

from freecad.PyrateWorkbench.TaskPanel_ClassWithOptimizableVariables_Edit import ClassWithOptimizableVariablesTaskPanelEdit


lc = LocalCoordinates.p()
fo = FunctionObject("f = lambda x, y: x + y", ["f"])
sh = Conic.p(lc, curv=0, cc=-1)

lc.decx.set_value(1.0)
lc.decy.set_value(2.0)
lc.decz.to_pickup((fo, "f"), (lc.decx, lc.decy))



dlg = ClassWithOptimizableVariablesTaskPanelEdit(sh)
FreeCADGui.Control.showDialog(dlg)
